import FreeCAD as App
import FreeCADGui as Gui
import Part
import time
from PySide import QtGui

##### PREAMBLE #####
t_cutout, ok = QtGui.QInputDialog.getDouble(
    None,
    "Cutout Wall Thickness",
    "What wall thickness should be left when hollowing cutouts, in mm?\nEnter 0 to leave cutouts solid.",
    0.0,
    0.0,
    1000.0,
    3
)

if not ok:
    raise Exception("Macro cancelled by user.")

# units are mm.
z_base = 1 # thickness of baseplate
z_index = 25.0 # height of indexing arms
z_ap = 25.0 # height of aperture negatives.

# I wouldn't go less than 0.5 for z_base, as the base becomes floppy and the indexing
# is therefore less certain. You could get away with shorter aperture and indexing bar
# heights, maybe as low as 22.

##### END PREAMBLE #####

##### HELPER FUNCTIONS #####
def get_wire(obj_name):

    obj = doc.getObject(obj_name)

    if obj is None:
        raise ValueError(f"No object named '{obj_name}' found.")

    shape = obj.Shape

    if not shape.isClosed():
        raise ValueError(f"'{obj_name}' is not closed.")

    return shape


def extrude_face(face, height, name):

    solid = face.extrude(App.Vector(0,0,height))

    feature = doc.addObject("Part::Feature", name)
    feature.Shape = solid

    return feature


def extrude_wire(obj_name, height, new_name):

    wire = get_wire(obj_name)
    face = Part.Face(wire)

    return extrude_face(face, height, new_name)

##### END HELPER FUNCTIONS #####

##### 1. IMPORT #####
doc = App.newDocument("SVG_Import")
Gui.ActiveDocument = Gui.getDocument(doc.Name)

initial_objects = len(doc.Objects)

Gui.runCommand('Std_Import')

while len(doc.Objects) <= initial_objects:
    time.sleep(0.5)

doc = App.ActiveDocument

##### END 1. IMPORT #####

##### 2. PAD INDEXING PLATE #####
pads = []

base = extrude_wire("Polyline", z_base, "Base")
pads.append(base)

left_index = extrude_wire("Polyline001", z_index, "LeftIndex")
right_index = extrude_wire("Polyline002", z_index, "RightIndex")

pads.append(left_index)
pads.append(right_index)

##### END 2. PAD INDEXING PLATE #####

##### 3. PAD REMAINING APERTURES #####
# This step is more complex - it takes the wall thickness parameter, if present,
# and attempts to do a part offset command. This command sucks and is super brittle in FreeCAD.
# That's why there's oceans of try/catch and ifs.
handled = {"Polyline", "Polyline001", "Polyline002"}

ap_count = 1

for obj in doc.Objects:
    #### SANITY CHECKS ####
    if obj.Name in handled:
        continue

    if "Polyline" not in obj.Name:
        continue

    if not hasattr(obj, "Shape"):
        continue

    if not obj.Shape or not obj.Shape.Edges:
        continue
    #### END SANITY CHECKS ####
    
    try:

        if not obj.Shape.isClosed():
            continue

        wire = obj.Shape
        face = Part.Face(wire)

        name = f"Aperture{ap_count:03d}"

        # Create outer pad
        outer_pad = extrude_face(face, z_ap, name + "_outer")

        final_pad = outer_pad

        # attempt to hollow
        if t_cutout > 0:

            try:
                offset_wire = wire.makeOffset2D(-t_cutout)
                offset_face = Part.Face(offset_wire)
                
                inner_pad = extrude_face(offset_face, z_ap, name + "_inner")
                hollow_shape = outer_pad.Shape.cut(inner_pad.Shape)
                hollow_obj = doc.addObject("Part::Feature", name)
                hollow_obj.Shape = hollow_shape

                # also try to cut out the base to save some printing time
                try:
                    base.Shape = base.Shape.cut(inner_pad.Shape)
                except Exception:
                    pass
                
                doc.removeObject(outer_pad.Name)
                doc.removeObject(inner_pad.Name)

                final_pad = hollow_obj

            except Exception as e:

                # just leave it alone if the offset failed
                doc.removeObject(outer_pad.Name)

                final_pad = extrude_face(face, z_ap, name)

        else:

            doc.removeObject(outer_pad.Name) # undo the eager wall face extrusion thing
            final_pad = extrude_face(face, z_ap, name)

        pads.append(final_pad)

        ap_count += 1

    except:
        # basically the only time this should trigger is if the extrusion failed, for some reason...
        pass

##### END 3. PAD REMAINING APERTURES #####

##### 4. CLEANUP #####
for obj in list(doc.Objects):

    if "Polyline" in obj.Name:
        doc.removeObject(obj.Name)

if pads:

    fused_shape = pads[0].Shape

    for p in pads[1:]:
        fused_shape = fused_shape.fuse(p.Shape)

    fused_obj = doc.addObject("Part::Feature", "UnifiedSolid")
    fused_obj.Shape = fused_shape

    for p in pads:
        if p.Name != fused_obj.Name:
            doc.removeObject(p.Name)

doc.recompute()
##### END 4. CLEANUP #####

##### 5. EXPORT #####
Gui.Selection.clearSelection()
Gui.Selection.addSelection(doc.Name, "UnifiedSolid")

Gui.runCommand('Std_Export')

##### END 5. EXPORT #####
