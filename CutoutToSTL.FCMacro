import FreeCAD as App
import FreeCADGui as Gui
import Part
import time
from PySide import QtGui, QtWidgets

##### PREAMBLE #####
t_cutout, ok = QtGui.QInputDialog.getDouble(
    None,
    "Cutout Wall Thickness",
    "What wall thickness should be left when hollowing cutouts, in mm?\nEnter 0 to leave cutouts solid.",
    0.0,
    0.0,
    1000.0,
    3
)

if not ok:
    raise Exception("Macro cancelled by user.")

reply = QtWidgets.QMessageBox.question(
    None,
    "Diverging Cut",
    "Attempt a diverging cut?",
    QtWidgets.QMessageBox.Yes | QtWidgets.QMessageBox.No,
    QtWidgets.QMessageBox.No
)

attempt_diverging_cut = (reply == QtWidgets.QMessageBox.Yes)
    
source_to_slot_distance_cm = None

if attempt_diverging_cut:
    value, ok = QtWidgets.QInputDialog.getDouble(
        None,
        "Source Distance",
        "Source to slot distance in cm?",
        95.0,   # default
        0.0,    # min
        10000.0, # max
        2       # decimals
    )
    
    if ok:
        source_to_slot_distance_cm = value
    else:
        raise Exception("Macro cancelled by user.")
        


# units are mm.
z_base = 1 # thickness of baseplate
z_index = 22 # height of indexing arms
z_ap = 20 # height of aperture negatives.

# I wouldn't go less than 0.5 for z_base, as the base becomes floppy and the indexing
# is therefore less certain. You could get away with shorter aperture and indexing bar
# heights, maybe as low as 22.

##### END PREAMBLE #####

##### HELPER FUNCTIONS #####
def get_wire(obj_name):

    obj = doc.getObject(obj_name)

    if obj is None:
        raise ValueError(f"No object named '{obj_name}' found.")

    shape = obj.Shape

    if not shape.isClosed():
        raise ValueError(f"'{obj_name}' is not closed.")

    return shape


def extrude_face(face, height, name):

    solid = face.extrude(App.Vector(0,0,height))

    feature = doc.addObject("Part::Feature", name)
    feature.Shape = solid

    return feature


def extrude_wire(obj_name, height, new_name):

    wire = get_wire(obj_name)
    face = Part.Face(wire)

    return extrude_face(face, height, new_name)

##### END HELPER FUNCTIONS #####

##### 1. IMPORT #####
doc = App.newDocument("SVG_Import")
Gui.ActiveDocument = Gui.getDocument(doc.Name)

initial_objects = len(doc.Objects)

Gui.runCommand('Std_Import')

while len(doc.Objects) <= initial_objects:
    time.sleep(0.5)

doc = App.ActiveDocument

##### END 1. IMPORT #####

##### 2. PAD INDEXING PLATE #####
pads = []

base = extrude_wire("Polyline", -z_base, "Base")
pads.append(base)

left_index = extrude_wire("Polyline001", z_index, "LeftIndex")
left_index_base = extrude_wire("Polyline001", -z_base, "LeftIndexBase")

right_index = extrude_wire("Polyline002", z_index, "RightIndex")
right_index_base = extrude_wire("Polyline001", -z_base, "RightIndexBase")

pads.append(left_index)
pads.append(left_index_base)

pads.append(right_index)
pads.append(right_index_base)

##### END 2. PAD INDEXING PLATE #####

##### 3. PAD REMAINING APERTURES #####
# This step is more complex - it takes the wall thickness parameter, if present,
# and attempts to do a part offset command. This command sucks and is super brittle in FreeCAD.
# That's why there's oceans of try/catch and ifs.
handled = {"Polyline", "Polyline001", "Polyline002"}

ap_count = 1

for obj in doc.Objects:
    #### SANITY CHECKS ####
    if obj.Name in handled:
        continue

    if "Polyline" not in obj.Name:
        continue

    if not hasattr(obj, "Shape"):
        continue

    if not obj.Shape or not obj.Shape.Edges:
        continue
    #### END SANITY CHECKS ####
    
    try:

        if not obj.Shape.isClosed():
            continue

        wire = obj.Shape
        face = Part.Face(wire)

        name = f"Aperture{ap_count:03d}"

        # Create outer pad (original behavior)
        outer_pad = extrude_face(face, z_ap, name + "_outer")
        final_pad = outer_pad

        if attempt_diverging_cut:

            z_source = 10 * source_to_slot_distance_cm
            scale = (z_source - z_ap) / z_source

            lower_outer_wire = wire

            lower_inner_wire = None
            if t_cutout > 0:
                try:
                    lower_inner_wire = wire.makeOffset2D(-t_cutout)
                except Exception:
                    lower_inner_wire = None

            center = App.Vector(150,150,z_source)

            # -----------------
            # Upper wires
            # -----------------
            upper_outer_wire = lower_outer_wire.copy()
            upper_outer_wire.scale(scale, center)

            if lower_inner_wire:
                upper_inner_wire = lower_inner_wire.copy()
                upper_inner_wire.scale(scale, center)

            # -----------------
            # Outer loft
            # -----------------
            outer_shape = Part.makeLoft(
                [lower_outer_wire, upper_outer_wire],
                True  # make solid
            )

            final_shape = outer_shape
            inner_shape = None

            # -----------------
            # Inner loft
            # -----------------
            if lower_inner_wire:
                
                inner_base_cutter = extrude_wire(lower_inner_wire.Name, -z_base, "BaseCutter")
                base.Shape = base.Shape.cut(inner_base_cutter)
                doc.removeObject(inner_base_cutter.Name)
                
                inner_shape = Part.makeLoft(
                    [lower_inner_wire, upper_inner_wire],
                    True
                )

                final_shape = outer_shape.cut(inner_shape)

            hollow_obj = doc.addObject("Part::Feature", name)
            hollow_obj.Shape = final_shape
            final_pad = hollow_obj

            doc.removeObject(outer_pad.Name)

        else:

            # original straight-extrusion logic
            if t_cutout > 0:

                try:
                    offset_wire = wire.makeOffset2D(-t_cutout)
                    offset_face = Part.Face(offset_wire)

                    inner_pad = extrude_face(offset_face, z_ap, name + "_inner")
                    hollow_shape = outer_pad.Shape.cut(inner_pad.Shape)

                    hollow_obj = doc.addObject("Part::Feature", name)
                    hollow_obj.Shape = hollow_shape

                    try:
                        base.Shape = base.Shape.cut(inner_pad.Shape)
                    except Exception:
                        pass

                    doc.removeObject(outer_pad.Name)
                    doc.removeObject(inner_pad.Name)

                    final_pad = hollow_obj

                except Exception:

                    doc.removeObject(outer_pad.Name)
                    final_pad = extrude_face(face, z_ap, name)
                    
        if final_pad:
            pads.append(final_pad)

    except:
        # basically the only time this should trigger is if the extrusion failed, for some reason...
        pass

##### END 3. PAD REMAINING APERTURES #####

##### 4. CLEANUP #####
for obj in list(doc.Objects):

    if "Polyline" in obj.Name:
        doc.removeObject(obj.Name)

if pads:

    fused_shape = pads[0].Shape

    for p in pads[1:]:
        fused_shape = fused_shape.fuse(p.Shape)

    fused_obj = doc.addObject("Part::Feature", "UnifiedSolid")
    fused_obj.Shape = fused_shape

    for p in pads:
        if p.Name != fused_obj.Name:
            doc.removeObject(p.Name)

doc.recompute()
##### END 4. CLEANUP #####

##### 5. EXPORT #####
Gui.Selection.clearSelection()
Gui.Selection.addSelection(doc.Name, "UnifiedSolid")

Gui.runCommand('Std_Export')

##### END 5. EXPORT #####
